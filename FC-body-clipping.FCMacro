"""FC-body-clipping.FCMacro

Version: 0.1
Author: Sedat Kuran
License: All right reserved (advised to release under LGPL2.1 as FreeCAD)
Copyright 2026 sedat_kuran

"""

import FreeCAD as App
import FreeCADGui as Gui
import Part
import math

from PySide.QtWidgets import (
    QColorDialog, QDockWidget, QDoubleSpinBox, QMessageBox, QLabel, QCheckBox,
    QRadioButton, QPushButton, QSlider, QSpinBox, QWidget,
    QHBoxLayout, QVBoxLayout,
)

from PySide.QtCore import Qt


class LiveSectionAnalyzer(QDockWidget):
    def __init__(self):
        super().__init__()
        self.setWindowTitle("Interactive Section Analysis")
        self.setAllowedAreas(Qt.LeftDockWidgetArea | Qt.RightDockWidgetArea)

        self.base_obj = self.get_selection()
        if not self.base_obj:
            return

        self.bbox = self.base_obj.Shape.BoundBox

        # Calculate bounding box dimensions
        self.x_len = self.bbox.XMax - self.bbox.XMin
        self.y_len = self.bbox.YMax - self.bbox.YMin
        self.z_len = self.bbox.ZMax - self.bbox.ZMin

        # Create all features once (for performance)
        self.section_feat = None
        self.edge_feat = None
        self.hatch_feat = None
        self.bg_feat = None
        self.frozen_group = None  # Group for frozen objects
        self.init_done = False

        self.init_ui()
        self.create_features()  # Create features once
        self.update_section()
        self.init_done = True

    def get_selection(self):
        sel = Gui.Selection.getSelection()
        if not sel:
            QMessageBox.warning(None, "Error", "Please select a part from the Tree View first!")
            return None
        return sel[0]

    def create_features(self):
        """Create all features once"""
        doc = App.ActiveDocument
        if not doc:
            return

        # Background object
        self.bg_feat = doc.addObject("Part::Feature", "Live_Section_Background")
        self.bg_feat.ViewObject.ShapeColor = self.base_obj.ViewObject.ShapeColor
        self.bg_feat.ViewObject.DisplayMode = "Shaded"
        self.bg_feat.ViewObject.Transparency = 70

        # Section fill (optional - default off)
        self.section_feat = doc.addObject("Part::Feature", "Live_Section_Fill")
        self.section_feat.ViewObject.ShapeColor = (0.75, 0.65, 0.68)
        self.section_feat.ViewObject.LineColor = (0.0, 0.0, 0.0)
        self.section_feat.ViewObject.LineWidth = 3.0
        self.section_feat.ViewObject.DisplayMode = "Shaded"
        self.section_feat.ViewObject.Transparency = 0
        self.section_feat.ViewObject.Visibility = False  # Default off

        # Section edge lines
        self.edge_feat = doc.addObject("Part::Feature", "Live_Section_Edges")
        self.edge_feat.ViewObject.LineColor = (0.0, 0.0, 0.0)
        self.edge_feat.ViewObject.LineWidth = 2.0
        self.edge_feat.ViewObject.DisplayMode = "Wireframe"
        self.edge_feat.ViewObject.Visibility = False
        self.edge_feat.ViewObject.PointSize = 1

        # Hatch lines
        self.hatch_feat = doc.addObject("Part::Feature", "Live_Hatch_Lines")
        self.hatch_feat.ViewObject.LineColor = (0.3, 0.3, 0.3)
        self.hatch_feat.ViewObject.LineWidth = 1.0
        self.hatch_feat.ViewObject.DisplayMode = "Wireframe"
        self.hatch_feat.ViewObject.Visibility = False
        self.hatch_feat.ViewObject.PointSize = 1

        doc.recompute()

    def init_ui(self):
        widget = QWidget()
        layout = QVBoxLayout(widget)

        # --- SECTION PLANE ---
        layout.addWidget(QLabel("<b>Section Plane:</b>"))
        self.radio_xy = QRadioButton("XY Plane")
        self.radio_xz = QRadioButton("XZ Plane")
        self.radio_yz = QRadioButton("YZ Plane (Default)")
        self.radio_yz.setChecked(True)

        layout.addWidget(self.radio_xy)
        layout.addWidget(self.radio_xz)
        layout.addWidget(self.radio_yz)

        # --- OFFSET (Slider + SpinBox) - Dynamic range based on bounding box ---
        layout.addWidget(QLabel("<b>Offset (Position):</b>"))

        # Calculate max offset range based on object size
        max_dim = max(self.x_len, self.y_len, self.z_len)
        self.offset_range = max_dim * 0.6  # 60% of max dimension
        self.offset_range = max(self.offset_range, 10.0)  # Minimum 10mm range

        # Horizontal layout for offset (slider + spinbox)
        offset_layout = QHBoxLayout()

        self.slider = QSlider(Qt.Horizontal)
        self.slider.setRange(-100, 100)
        self.slider.setValue(0)
        self.slider.setTickPosition(QSlider.TicksBelow)
        self.slider.setTickInterval(10)
        offset_layout.addWidget(self.slider)

        # SpinBox for precise value entry
        self.offset_spin = QDoubleSpinBox()
        self.offset_spin.setRange(-self.offset_range, self.offset_range)
        self.offset_spin.setValue(0.0)
        self.offset_spin.setSingleStep(self.offset_range / 20.0)  # 20 steps
        self.offset_spin.setSuffix(" mm")
        self.offset_spin.setDecimals(1)
        self.offset_spin.setMaximumWidth(100)
        offset_layout.addWidget(self.offset_spin)

        layout.addLayout(offset_layout)

        # Show current range info
        range_label = QLabel(f"<i>Offset range: ±{self.offset_range:.1f} mm (based on object size)</i>")
        range_label.setStyleSheet("color: #666; font-size: 10px;")
        layout.addWidget(range_label)

        # --- BACKGROUND SETTINGS ---
        layout.addWidget(QLabel("<b>Background Settings:</b>"))

        # Transparency
        trans_layout = QHBoxLayout()
        trans_layout.addWidget(QLabel("Transparency (%):"))
        self.spin_trans = QSpinBox()
        self.spin_trans.setRange(0, 100)
        self.spin_trans.setValue(70)
        trans_layout.addWidget(self.spin_trans)
        trans_layout.addStretch()
        layout.addLayout(trans_layout)

        # Background Mirror
        mirror_layout = QHBoxLayout()
        self.chk_mirror_bg = QCheckBox("Mirror Background")
        self.chk_mirror_bg.setChecked(False)
        mirror_layout.addWidget(self.chk_mirror_bg)
        mirror_layout.addStretch()
        layout.addLayout(mirror_layout)

        # --- SECTION FILL (OPTIONAL) ---
        layout.addWidget(QLabel("<b>Section Fill (Optional):</b>"))

        self.chk_section_fill = QCheckBox("Show Section Fill")
        self.chk_section_fill.setChecked(False)  # Default off
        layout.addWidget(self.chk_section_fill)

        # Section fill color
        fill_color_layout = QHBoxLayout()
        fill_color_layout.addWidget(QLabel("Color:"))
        self.fill_color_btn = QPushButton()
        self.fill_color_btn.setStyleSheet("background-color: rgb(191, 166, 173); max-width: 50px;")
        self.fill_color_btn.clicked.connect(lambda: self.pick_color(self.fill_color_btn, "fill"))
        fill_color_layout.addWidget(self.fill_color_btn)
        fill_color_layout.addStretch()
        layout.addLayout(fill_color_layout)

        # --- EDGE LINE SETTINGS ---
        layout.addWidget(QLabel("<b>Edge Line Settings:</b>"))

        self.chk_edges = QCheckBox("Show Edge Lines")
        self.chk_edges.setChecked(True)
        layout.addWidget(self.chk_edges)

        # Edge color
        edge_color_layout = QHBoxLayout()
        edge_color_layout.addWidget(QLabel("Color:"))
        self.edge_color_btn = QPushButton()
        self.edge_color_btn.setStyleSheet("background-color: rgb(0, 0, 0); max-width: 50px;")
        self.edge_color_btn.clicked.connect(lambda: self.pick_color(self.edge_color_btn, "edge"))
        edge_color_layout.addWidget(self.edge_color_btn)
        edge_color_layout.addStretch()
        layout.addLayout(edge_color_layout)

        # Edge width
        edge_width_layout = QHBoxLayout()
        edge_width_layout.addWidget(QLabel("Width:"))
        self.edge_width_spin = QDoubleSpinBox()
        self.edge_width_spin.setRange(0.5, 10.0)
        self.edge_width_spin.setValue(2.0)
        self.edge_width_spin.setSingleStep(0.5)
        edge_width_layout.addWidget(self.edge_width_spin)
        edge_width_layout.addStretch()
        layout.addLayout(edge_width_layout)

        # --- HATCH SETTINGS ---
        layout.addWidget(QLabel("<b>Hatch Settings:</b>"))

        self.chk_hatch = QCheckBox("Enable Hatch")
        self.chk_hatch.setChecked(True)
        layout.addWidget(self.chk_hatch)

        # Hatch spacing
        spacing_layout = QHBoxLayout()
        spacing_layout.addWidget(QLabel("Spacing (mm):"))
        self.spin_spacing = QDoubleSpinBox()
        self.spin_spacing.setRange(0.5, 20.0)
        self.spin_spacing.setValue(3.0)
        self.spin_spacing.setSingleStep(0.5)
        spacing_layout.addWidget(self.spin_spacing)
        spacing_layout.addStretch()
        layout.addLayout(spacing_layout)

        # Hatch color
        hatch_color_layout = QHBoxLayout()
        hatch_color_layout.addWidget(QLabel("Color:"))
        self.hatch_color_btn = QPushButton()
        self.hatch_color_btn.setStyleSheet("background-color: rgb(77, 77, 77); max-width: 50px;")
        self.hatch_color_btn.clicked.connect(lambda: self.pick_color(self.hatch_color_btn, "hatch"))
        hatch_color_layout.addWidget(self.hatch_color_btn)
        hatch_color_layout.addStretch()
        layout.addLayout(hatch_color_layout)

        # Hatch width
        hatch_width_layout = QHBoxLayout()
        hatch_width_layout.addWidget(QLabel("Width:"))
        self.hatch_width_spin = QDoubleSpinBox()
        self.hatch_width_spin.setRange(0.5, 5.0)
        self.hatch_width_spin.setValue(1.0)
        self.hatch_width_spin.setSingleStep(0.5)
        hatch_width_layout.addWidget(self.hatch_width_spin)
        hatch_width_layout.addStretch()
        layout.addLayout(hatch_width_layout)

        # Hatch point size
        hatch_point_layout = QHBoxLayout()
        hatch_point_layout.addWidget(QLabel("Point Size (px):"))
        self.hatch_point_spin = QSpinBox()
        self.hatch_point_spin.setRange(0, 10)
        self.hatch_point_spin.setValue(1)
        self.hatch_point_spin.setSingleStep(1)
        hatch_point_layout.addWidget(self.hatch_point_spin)
        hatch_point_layout.addStretch()
        layout.addLayout(hatch_point_layout)

        # --- FREEZE BUTTON ---
        layout.addWidget(QLabel("<b>Freeze Section:</b>"))
        self.btn_freeze = QPushButton("❄️ Freeze Section (Simple Copy with Folder)")
        self.btn_freeze.setStyleSheet("""
            QPushButton {
                background-color: #4CAF50;
                color: white;
                font-weight: bold;
                padding: 8px;
                border-radius: 4px;
            }
            QPushButton:hover {
                background-color: #45a049;
            }
        """)
        self.btn_freeze.clicked.connect(self.freeze_section)
        layout.addWidget(self.btn_freeze)

        # --- CONNECTIONS ---
        self.radio_xy.toggled.connect(self.update_section)
        self.radio_xz.toggled.connect(self.update_section)
        self.radio_yz.toggled.connect(self.update_section)
        self.slider.valueChanged.connect(self.on_slider_changed)
        self.offset_spin.valueChanged.connect(self.on_spin_changed)
        self.spin_trans.valueChanged.connect(self.update_section)
        self.chk_mirror_bg.stateChanged.connect(self.update_section)
        self.chk_section_fill.stateChanged.connect(self.update_section)
        self.fill_color_btn.clicked.connect(lambda: self.pick_color(self.fill_color_btn, "fill"))
        self.chk_hatch.stateChanged.connect(self.update_section)
        self.spin_spacing.valueChanged.connect(self.update_section)
        self.chk_edges.stateChanged.connect(self.update_section)
        self.edge_width_spin.valueChanged.connect(self.update_edge_style)
        self.hatch_width_spin.valueChanged.connect(self.update_hatch_style)
        self.hatch_point_spin.valueChanged.connect(self.update_hatch_point_size)

        # --- CLOSE BUTTON ---
        self.btn_close = QPushButton("Close Analysis")
        self.btn_close.clicked.connect(self.close)
        layout.addWidget(self.btn_close)

        layout.addStretch()
        widget.setLayout(layout)
        self.setWidget(widget)
        Gui.getMainWindow().addDockWidget(Qt.LeftDockWidgetArea, self)

    def on_slider_changed(self, value):
        """Update spinbox when slider changes"""
        # Map slider (-100 to 100) to offset range
        mapped_value = (value / 100.0) * self.offset_range
        self.offset_spin.setValue(mapped_value)
        self.update_section()

    def on_spin_changed(self, value):
        """Update slider when spinbox changes"""
        # Map offset value to slider range (-100 to 100)
        slider_value = int((value / self.offset_range) * 100)
        slider_value = max(-100, min(100, slider_value))  # Clamp to range
        self.slider.setValue(slider_value)
        self.update_section()

    def pick_color(self, button, target):
        """Open color picker dialog"""
        color_dialog = QColorDialog()
        current_color = button.palette().button().color()
        color_dialog.setCurrentColor(current_color)

        if color_dialog.exec_():
            color = color_dialog.currentColor()
            r, g, b = color.red()/255.0, color.green()/255.0, color.blue()/255.0
            button.setStyleSheet(f"background-color: rgb({color.red()}, {color.green()}, {color.blue()}); max-width: 50px;")

            if target == "edge":
                self.edge_feat.ViewObject.LineColor = (r, g, b)
            elif target == "hatch":
                self.hatch_feat.ViewObject.LineColor = (r, g, b)
            elif target == "fill":
                self.section_feat.ViewObject.ShapeColor = (r, g, b)

            App.ActiveDocument.recompute()
            Gui.updateGui()

    def update_edge_style(self):
        """Update edge width"""
        if self.edge_feat:
            self.edge_feat.ViewObject.LineWidth = self.edge_width_spin.value()
            App.ActiveDocument.recompute()
            Gui.updateGui()

    def update_hatch_style(self):
        """Update hatch width"""
        if self.hatch_feat:
            self.hatch_feat.ViewObject.LineWidth = self.hatch_width_spin.value()
            App.ActiveDocument.recompute()
            Gui.updateGui()

    def update_hatch_point_size(self):
        """Update hatch point size (start and end points)"""
        if self.hatch_feat:
            self.hatch_feat.ViewObject.PointSize = self.hatch_point_spin.value()
            App.ActiveDocument.recompute()
            Gui.updateGui()

    def freeze_section(self):
        """Freeze current section view using SimpleCopy with folder"""
        doc = App.ActiveDocument
        if not doc:
            return

        try:
            # Determine plane type (for naming)
            if self.radio_yz.isChecked():
                plane_name = "YZ"
            elif self.radio_xz.isChecked():
                plane_name = "XZ"
            else:
                plane_name = "XY"

            offset_val = self.offset_spin.value()

            # Create new group or update existing
            group_name = f"Frozen_Section_{plane_name}_Offset_{offset_val:.1f}"

            # Delete old group
            if self.frozen_group and doc.getObject(self.frozen_group.Name):
                # Delete all objects in group
                for obj in self.frozen_group.Group:
                    try:
                        doc.removeObject(obj.Name)
                    except:
                        pass
                try:
                    doc.removeObject(self.frozen_group.Name)
                except:
                    pass

            # Create new group
            self.frozen_group = doc.addObject("App::DocumentObjectGroup", group_name)
            self.frozen_group.Label = f"Frozen Section ({plane_name}, Offset: {offset_val:.1f} mm)"

            # Copy section elements
            copied_objects = []

            # 1. Copy background object
            if self.bg_feat and self.bg_feat.Shape:
                bg_copy = doc.addObject("Part::Feature", f"Section_Background_{plane_name}")
                bg_copy.Shape = self.bg_feat.Shape
                bg_copy.ViewObject.ShapeColor = self.bg_feat.ViewObject.ShapeColor
                bg_copy.ViewObject.DisplayMode = "Shaded"
                bg_copy.ViewObject.Transparency = self.spin_trans.value()
                copied_objects.append(bg_copy)

            # 2. Copy section fill (if visible)
            if self.chk_section_fill.isChecked() and self.section_feat and self.section_feat.Shape:
                fill_copy = doc.addObject("Part::Feature", f"Section_Fill_{plane_name}")
                fill_copy.Shape = self.section_feat.Shape
                fill_copy.ViewObject.ShapeColor = self.section_feat.ViewObject.ShapeColor
                fill_copy.ViewObject.LineColor = self.section_feat.ViewObject.LineColor
                fill_copy.ViewObject.LineWidth = self.section_feat.ViewObject.LineWidth
                fill_copy.ViewObject.DisplayMode = "Shaded"
                fill_copy.ViewObject.Transparency = 0
                copied_objects.append(fill_copy)

            # 3. Copy edge lines
            if self.chk_edges.isChecked() and self.edge_feat and self.edge_feat.Shape:
                edge_copy = doc.addObject("Part::Feature", f"Section_Edges_{plane_name}")
                edge_copy.Shape = self.edge_feat.Shape
                edge_copy.ViewObject.LineColor = self.edge_feat.ViewObject.LineColor
                edge_copy.ViewObject.LineWidth = self.edge_feat.ViewObject.LineWidth
                edge_copy.ViewObject.DisplayMode = "Wireframe"
                edge_copy.ViewObject.PointSize = 1
                copied_objects.append(edge_copy)

            # 4. Copy hatch lines
            if self.chk_hatch.isChecked() and self.hatch_feat and self.hatch_feat.Shape:
                hatch_copy = doc.addObject("Part::Feature", f"Section_Hatch_{plane_name}")
                hatch_copy.Shape = self.hatch_feat.Shape
                hatch_copy.ViewObject.LineColor = self.hatch_feat.ViewObject.LineColor
                hatch_copy.ViewObject.LineWidth = self.hatch_feat.ViewObject.LineWidth
                hatch_copy.ViewObject.DisplayMode = "Wireframe"
                hatch_copy.ViewObject.PointSize = self.hatch_point_spin.value()
                copied_objects.append(hatch_copy)

            if not copied_objects:
                QMessageBox.warning(None, "Warning", "No section elements found to copy!")
                # Delete empty group
                try:
                    doc.removeObject(self.frozen_group.Name)
                    self.frozen_group = None
                except:
                    pass
                return

            # Add all copied objects to group
            for obj in copied_objects:
                self.frozen_group.addObject(obj)

            # Make group visible
            self.frozen_group.ViewObject.Visibility = True

            # Select group in tree view
            Gui.Selection.clearSelection()
            Gui.Selection.addSelection(self.frozen_group)

            doc.recompute()
            Gui.updateGui()

            # Success message
            QMessageBox.information(
                None,
                "Success",
                f"Section successfully frozen!\n"
                f"Group name: {self.frozen_group.Label}\n"
                f"Element count: {len(copied_objects)}\n"
                f"Plane: {plane_name}, Offset: {offset_val:.1f} mm\n\n"
                f"📁 Contents:\n" +
                "\n".join([f"  • {obj.Label}" for obj in copied_objects])
            )

        except Exception as e:
            App.Console.PrintError(f"Freeze Error: {str(e)}\n")
            QMessageBox.critical(None, "Error", f"Error while freezing section:\n{str(e)}")

    def generate_hatch_lines_optimized(self, face, plane_type, center_pos, spacing):
        """Optimized hatch generation - only generate lines within face boundaries"""
        lines = []

        # Get face 2D bounding box
        bbox = face.BoundBox

        # Determine u,v axes based on plane
        if plane_type == "YZ":
            u_min, u_max = bbox.YMin - 2, bbox.YMax + 2
            v_min, v_max = bbox.ZMin - 2, bbox.ZMax + 2
        elif plane_type == "XZ":
            u_min, u_max = bbox.XMin - 2, bbox.XMax + 2
            v_min, v_max = bbox.ZMin - 2, bbox.ZMax + 2
        else:  # XY
            u_min, u_max = bbox.XMin - 2, bbox.XMax + 2
            v_min, v_max = bbox.YMin - 2, bbox.YMax + 2

        # Calculate step
        step = spacing * math.sqrt(2)
        current = u_min

        # Generate hatch lines
        while current < u_max + (v_max - v_min):
            # Line start and end points
            if plane_type == "YZ":
                p1 = App.Vector(center_pos, current, v_min)
                p2 = App.Vector(center_pos, current - (v_max - v_min), v_max)
            elif plane_type == "XZ":
                p1 = App.Vector(current, center_pos, v_min)
                p2 = App.Vector(current - (v_max - v_min), center_pos, v_max)
            else:
                p1 = App.Vector(current, v_min, center_pos)
                p2 = App.Vector(current - (v_max - v_min), v_max, center_pos)

            try:
                # Create line and intersect with face
                line_shape = Part.makeLine(p1, p2)
                common_part = face.common(line_shape)
                if common_part.Edges:
                    lines.append(common_part)
            except:
                pass

            current += step

        return lines

    def update_section(self):
        doc = App.ActiveDocument
        if not doc or not self.base_obj:
            return

        # Hide main object
        self.base_obj.ViewObject.Visibility = False

        # Get offset value from spinbox (already in mm)
        offset_val = self.offset_spin.value()

        x_len = self.x_len
        y_len = self.y_len
        z_len = self.z_len
        max_dim = max(x_len, y_len, z_len) * 3

        # Determine plane type
        if self.radio_yz.isChecked():
            plane_type = "YZ"
            center_pos = self.bbox.Center.x + offset_val  # Direct mm offset
            plane_base = App.Vector(center_pos, self.bbox.Center.y, self.bbox.Center.z)
            plane_normal = App.Vector(1, 0, 0)
        elif self.radio_xz.isChecked():
            plane_type = "XZ"
            center_pos = self.bbox.Center.y + offset_val  # Direct mm offset
            plane_base = App.Vector(self.bbox.Center.x, center_pos, self.bbox.Center.z)
            plane_normal = App.Vector(0, 1, 0)
        else:
            plane_type = "XY"
            center_pos = self.bbox.Center.z + offset_val  # Direct mm offset
            plane_base = App.Vector(self.bbox.Center.x, self.bbox.Center.y, center_pos)
            plane_normal = App.Vector(0, 0, 1)

        try:
            # Create cutter box
            cutter_box = Part.makeBox(max_dim, max_dim, max_dim)
            cutter_box.translate(App.Vector(-max_dim/2, -max_dim/2, 0))

            if plane_type == "YZ":
                cutter_box.rotate(App.Vector(0,0,0), App.Vector(0,1,0), 90)
            elif plane_type == "XZ":
                cutter_box.rotate(App.Vector(0,0,0), App.Vector(1,0,0), -90)

            cutter_box.translate(plane_base)

            # Calculate background solid
            cut_solid = self.base_obj.Shape.cut(cutter_box)

            # Mirror background if enabled
            if self.chk_mirror_bg.isChecked():
                # Mirror based on section plane
                mirror_matrix = App.Matrix()
                if plane_type == "YZ":
                    mirror_matrix.scale(-1, 1, 1)
                    mirror_matrix.move(App.Vector(2 * plane_base.x, 0, 0))
                elif plane_type == "XZ":
                    mirror_matrix.scale(1, -1, 1)
                    mirror_matrix.move(App.Vector(0, 2 * plane_base.y, 0))
                else:  # XY
                    mirror_matrix.scale(1, 1, -1)
                    mirror_matrix.move(App.Vector(0, 0, 2 * plane_base.z))

                mirrored_solid = cut_solid.transformGeometry(mirror_matrix)
                cut_solid = mirrored_solid

            # Find section faces
            cut_faces = []
            for face in cut_solid.Faces:
                face_center = face.CenterOfMass
                val = face_center.x if plane_type == "YZ" else (face_center.y if plane_type == "XZ" else face_center.z)
                if abs(val - center_pos) < 1e-2:
                    cut_faces.append(face)

            if cut_faces:
                # --- UPDATE BACKGROUND ---
                self.bg_feat.Shape = cut_solid
                self.bg_feat.ViewObject.Transparency = self.spin_trans.value()
                self.bg_feat.ViewObject.Visibility = True

                # --- SECTION FILL (OPTIONAL) ---
                if self.chk_section_fill.isChecked():
                    self.section_feat.Shape = Part.Compound(cut_faces)
                    self.section_feat.ViewObject.Visibility = True
                else:
                    self.section_feat.ViewObject.Visibility = False

                # --- EDGE LINES ---
                if self.chk_edges.isChecked():
                    # Collect all edges
                    edges = []
                    for face in cut_faces:
                        for edge in face.Edges:
                            edges.append(edge)

                    if edges:
                        # Use removeSplitter for cleaner look
                        section_shape = Part.Compound(cut_faces)
                        clean_edges = section_shape.removeSplitter().Edges
                        if clean_edges:
                            self.edge_feat.Shape = Part.Compound(clean_edges)
                        else:
                            self.edge_feat.Shape = Part.Compound(edges)
                        self.edge_feat.ViewObject.Visibility = True
                    else:
                        self.edge_feat.ViewObject.Visibility = False
                else:
                    self.edge_feat.ViewObject.Visibility = False

                # --- HATCH LINES ---
                if self.chk_hatch.isChecked():
                    all_hatch_lines = []
                    spacing = self.spin_spacing.value()

                    for face in cut_faces:
                        lines = self.generate_hatch_lines_optimized(face, plane_type, center_pos, spacing)
                        all_hatch_lines.extend(lines)

                    if all_hatch_lines:
                        self.hatch_feat.Shape = Part.Compound(all_hatch_lines)
                        self.hatch_feat.ViewObject.Visibility = True
                        self.hatch_feat.ViewObject.PointSize = self.hatch_point_spin.value()
                    else:
                        self.hatch_feat.ViewObject.Visibility = False
                else:
                    self.hatch_feat.ViewObject.Visibility = False

        except Exception as e:
            App.Console.PrintError(f"Section Error: {str(e)}\n")

        doc.recompute()
        Gui.updateGui()

    def closeEvent(self, event):
        """Cleanup on close"""
        if self.base_obj:
            self.base_obj.ViewObject.Visibility = True

        doc = App.ActiveDocument
        if doc:
            # Delete all features except frozen group
            for feat in [self.section_feat, self.edge_feat, self.hatch_feat, self.bg_feat]:
                if feat and doc.getObject(feat.Name):
                    try:
                        doc.removeObject(feat.Name)
                    except:
                        pass
            doc.recompute()

        super().closeEvent(event)

# Run the macro
try:
    section_analyzer.close()
except NameError:
    pass

section_analyzer = LiveSectionAnalyzer()
